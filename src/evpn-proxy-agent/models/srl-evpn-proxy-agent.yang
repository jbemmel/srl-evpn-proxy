module srl-evpn-proxy-agent {

    yang-version "1.1";

    namespace "urn:srl_nokia_demo/evpn-proxy";
    // Put it in the same namespace, so we can read EVI config? Does not work
    // namespace "urn:srl_nokia/network-instance/protocols/bgp-evpn";

    prefix "demo_evpn_proxy";

    import srl_nokia-common {
        prefix srl_nokia-comm;
    }
    import srl_nokia-network-instance {
        prefix srl_nokia-netinst;
    }
    import srl_nokia-bgp-evpn {
        prefix srl_nokia-bgp-evpn;
    }
    import srl_nokia-interfaces {
        prefix srl_nokia-if;
    }
    import srl_nokia-if-ip {
        prefix srl_nokia-if-ip;
    }
    import srl_nokia-extensions {
        prefix srl_nokia-ext;
    }
    import srl_nokia-tunnel-interfaces {
        prefix srl_nokia-tun;
    }
    import srl_nokia-features { prefix srl-feat; }

    revision "2021-08-21" {
        description "Initial revision";
        reference "TBD";
    }

    feature "dataplane-learning" {
      description "Use ARP snooping based on eBPF to learn MAC addresses and static VTEP IPs";
    }

    grouping evpn-proxy-protocol {
        description "Configure EVPN Proxy";

        container vxlan-agent {
            if-feature "srl-feat:vxlan and srl-feat:evpn";

            presence "Configure BGP EVPN proxy agent for static VXLAN integration";
            must "../../srl_nokia-netinst:type = 'srl_nokia-netinst:default'" {
              error-message "VXLAN agent must be configured in the default network instance";
            }

            leaf admin-state {
                type srl_nokia-comm:admin-state;
                default "enable";

                description "Administratively enable or disable EVPN proxy functionality";
            }

            leaf source-address {
              mandatory true;
              type srl_nokia-comm:ip-address;
              description "Local loopback IP to connect from";
            }

            leaf peer-address {
              type srl_nokia-comm:ip-address;
              default "127.0.0.1";
              description "Remote IP to connect to, default localhost";
            }

            leaf local-as {
              type uint32 {
                range "1..4294967295";
              }
              default 65535;
              description "Local AS to use in BGP EVPN peering";
            }

            leaf peer-as {
              type uint32 {
                range "1..4294967295";
              }
              default 65535;
              description "Peer AS to use in BGP EVPN peering";
            }

            leaf local-preference {
              type uint32;
              default 100;
              description "Local preference to use for advertising EVPN MAC routes, default 100";
            }

            container proof-of-concept {
              // if-feature dataplane-learning;
              srl_nokia-ext:show-importance high; // affects info | as table
              presence "Configure Proof-of-Concept features";
              description "Set of features intended as Proof-of-Concept (only)";

              leaf-list vxlan-arp-learning-interfaces {
                type string;
                description "Interface(s) to listen on for VXLAN ARP packets, like 'e1-1'.
                             Leave empty to disable ARP/VTEP learning";

              }
              leaf include-ip {
                type boolean;
                default true;
                description "Whether to include the IP address in EVPN RT2 MAC routes, default true";
              }

              leaf auto-discover-static-vteps {
                type boolean;
                default true;
                description "Whether to announce EVPN routes for static VTEPs that are not explicitly configured";
              }

              leaf ecmp-path-probes {
                type boolean;
                default true;
                description "Enable experimental ARP-in-VXLAN probe packets to measure path diversity and latency";
              }
            }

            leaf oper-state {
              config false;
              srl_nokia-ext:show-importance "high";
              type srl_nokia-comm:oper-state;
              description "This leaf contains the operational state of this VXLAN proxy agent";
            }
        }
    }

    grouping evpn-proxy-state {
      container vxlan-proxy {
        description "Operational state for VXLAN EVPN proxy agent";

        // Only supported on SRL platforms that have both VXLAN and EVPN
        if-feature "srl-feat:vxlan and srl-feat:evpn";

        presence "BGP EVPN proxy state";
        config false;

        list static-vtep {
          key "vtep_ip";

          leaf vtep_ip {
            type srl_nokia-comm:ip-address;
            srl_nokia-ext:show-importance "high";
            description "VXLAN source/destination IP for this VTEP";
          }

          leaf last-update {
            type srl_nokia-comm:date-and-time-delta;
            srl_nokia-ext:show-importance "high";
            description "The date and time of the last update of this VTEP";
          }

          leaf dynamic {
            type boolean;
            description "Indicates this VTEP IP was learned from dataplane ARP messages";
          }

          list mac-vrf {
            key "name";
            leaf name {
              type leafref {
                path "/srl_nokia-netinst:network-instance/srl_nokia-netinst:name";
              }
            }
            leaf evi {
               type uint32 {
                 range "1..65535";
               }
               srl_nokia-ext:show-importance "high";
               description "EVPN instance enabled for this VTEP";
            }
            leaf vni {
              type uint32 {
                range "1..16777215";
              }
              srl_nokia-ext:show-importance "high";
              description "VXLAN Network Identifier enabled for this VTEP";
            }
            list mac {
              key "address";
              description "macs learnt on the bridging instance";
              leaf address {
                type srl_nokia-comm:mac-address;
              }
              leaf last-update {
                type srl_nokia-comm:date-and-time-delta;
                srl_nokia-ext:show-importance "high";
                description "The date and time of the last update of this mac";
              }
              leaf ip {
                type srl_nokia-comm:ip-address;
              }
              leaf evpn-mac-mobility {
                description "EVPN MAC mobility sequence number used/seen";
                type uint32;
              }
            }
          }
        }

        leaf-list evpn-vteps {
          type srl_nokia-comm:ip-address;
        }

        list path-probe-to {
          key "mac-vrf vtep-ip vni";

          leaf mac-vrf {
            type leafref {
              // This allows auto-completion to work in the CLI
              path "/srl_nokia-netinst:network-instance/srl_nokia-netinst:name";
            }
            srl_nokia-ext:show-importance "high";
            description "Name of mac-vrf used for this probe";
          }

          leaf vtep-ip {
            type srl_nokia-comm:ip-address;
            srl_nokia-ext:show-importance "high";
            description "IP of remote VTEP";
          }

          leaf vni {
            type uint32 {
              range "1..16777215";
            }
            srl_nokia-ext:show-importance "high";
            description "VNI used for this probe";
          }

          list at {
            key timestamp;
            // ordered-by user;

            leaf timestamp {
              type srl_nokia-comm:date-and-time-delta;
              srl_nokia-ext:show-importance "high";
              description "The date and time of the last update of this mac";
            }

            leaf result {
              type string;
            }
            leaf latency { type uint32; description "Average RTT in us across all paths"; }
            leaf sent { type uint8; description "Number of probes sent"; }
            leaf lost { type uint8; description "Number of probes lost"; }
            leaf-list probes { type uint32; }
            leaf-list peer-uplinks {
              description "Distribution of probes over uplink interfaces";
              type string;
            }
          }
        }
      }
    }

    augment "/srl_nokia-netinst:network-instance/srl_nokia-netinst:protocols" {
        uses evpn-proxy-protocol;
    }

    // Need to get the evi value for generating correct auto RD/RT
    augment "/srl_nokia-netinst:network-instance/srl_nokia-netinst:protocols/srl_nokia-netinst:bgp-evpn/srl_nokia-bgp-evpn:bgp-instance" {
        container vxlan-agent {
          if-feature "srl-feat:vxlan and srl-feat:evpn";
          presence "VXLAN agent configuration";

          description "Enable learning and advertisement of proxy EVPN routes for this instance";

          must "../../../../srl_nokia-netinst:type = 'srl_nokia-netinst:mac-vrf'" {
            error-message "VXLAN agent can only be enabled for L2 mac-vrf";
          }

          leaf admin-state {
              type srl_nokia-comm:admin-state;
              default "enable";

              description "Administratively enable or disable VXLAN agent functionality for this mac-vrf";
          }

          // Best way I could find to reference existing evi value from config
          leaf evi {
             description "Copy of the EVPN instance(evi) for this mac-vrf, used for auto-RD/RT";

             type uint32 {
               range "1..65535";
             }
             mandatory true;
             must ". = ../../srl_nokia-bgp-evpn:evi" {
               error-message "EVI must match bgp-evpn config";
             }
          }

          leaf vni {
            description "Copy of the VNI for this service";
            type uint32 {
              range "1..16777215";
            }
            mandatory true;
            must ". = /srl_nokia-tun:tunnel-interface[srl_nokia-tun:name=substring-before(../../srl_nokia-bgp-evpn:vxlan-interface, '.')]/srl_nokia-tun:vxlan-interface[srl_nokia-tun:index=substring-after(../../srl_nokia-tun:vxlan-interface, '.')]/srl_nokia-tun:ingress/srl_nokia-tun:vni" {
              error-message "VNI must match ingress vni on the vxlan-interface";
            }
          }

          list static-vtep {
            description "List of remote VTEPs for static non-EVPN peers (IPv4)";
            key vtep-ip;
            leaf vtep-ip {
              type srl_nokia-comm:ipv4-address;
            }
            leaf-list static-macs {
              description "Optional list of endpoint MAC addresses hosted by this VTEP";
              // type srl_nokia-comm:mac-address;
              // Use custom pattern to exclude broadcast/multicast MACs
              type string {
                pattern '[0-9a-fA-F][02468aceACE](:[0-9a-fA-F]{2}){5}';

                // Exclude VRRP MACs
                pattern '00:00:5[eE]:00:01:.*' {
                  modifier invert-match;
                  error-message "VRRP MACs should not be defined statically";
                }
              }
            }
          }


        }
    }

    uses evpn-proxy-state;
}
